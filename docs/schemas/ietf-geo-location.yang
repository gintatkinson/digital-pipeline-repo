module ietf-geo-location {
  yang-version 1.1;
  namespace "urn:ietf:params:xml:ns:yang:ietf-geo-location";
  prefix geo;

  organization
    "IETF NETMOD (Network Modeling) Working Group";

  contact
    "WG Web:   <https://datatracker.ietf.org/wg/netmod/>
     WG List:  <mailto:netmod@ietf.org>";

  description
    "This module defines a generic location grouping for geographic coordinates.";

  revision 2022-02-11 {
    description
      "Initial revision.";
    reference
      "RFC 9179: A YANG Data Model for Geographic Location";
  }

  container geo-location {
    description
      "Geographic location information container.";

    container control-status {
      description
        "Control status bits and configuration flags.";

      leaf commit-flag {
        type boolean;
        description "Commit trigger update.";
      }
    }

    container geodetic-system {
      description
        "Geodetic datum and system parameters.";

      leaf datum-id {
        type string;
        description "Geodetic Datum ID identifier.";
      }
    }

    container location {
      description
        "Coordinate geometry representations.";

      leaf dim_0 {
        type string;
        description "Latitude or Cartesian X dimension.";
      }

      leaf dim_1 {
        type string;
        description "Longitude or Cartesian Y dimension.";
      }

      leaf dim_2 {
        type string;
        description "Altitude or Cartesian Z dimension.";
      }
    }

    leaf validity-limit {
      type string;
      description "Validity boundary timestamp.";
    }
  }
}
